---
-- Copyright (c) 2014 Jason Lingle
-- All rights reserved.
--
-- Redistribution and use in source and binary forms, with or without
-- modification, are permitted provided that the following conditions
-- are met:
-- 1. Redistributions of source code must retain the above copyright
--    notice, this list of conditions and the following disclaimer.
-- 2. Redistributions in binary form must reproduce the above copyright
--    notice, this list of conditions and the following disclaimer in the
--    documentation and/or other materials provided with the distribution.
-- 3. Neither the name of the author nor the names of its contributors
--    may be used to endorse or promote products derived from this software
--    without specific prior written permission.
--
-- THIS SOFTWARE IS PROVIDED BY THE AUTHOR ``AS IS'' AND ANY EXPRESS OR
-- IMPLIED WARRANTIES, INCLUDING, BUT NOT LIMITED TO, THE IMPLIED WARRANTIES
-- OF MERCHANTABILITY AND FITNESS FOR A PARTICULAR PURPOSE ARE DISCLAIMED.
-- IN NO EVENT SHALL THE AUTHOR BE LIABLE FOR ANY DIRECT, INDIRECT,
-- INCIDENTAL, SPECIAL, EXEMPLARY, OR CONSEQUENTIAL DAMAGES (INCLUDING, BUT
-- NOT LIMITED TO, PROCUREMENT OF SUBSTITUTE GOODS OR SERVICES; LOSS OF USE,
-- DATA, OR PROFITS; OR BUSINESS INTERRUPTION) HOWEVER CAUSED AND ON ANY
-- THEORY OF LIABILITY, WHETHER IN CONTRACT, STRICT LIABILITY, OR TORT
-- (INCLUDING NEGLIGENCE OR OTHERWISE) ARISING IN ANY WAY OUT OF THE USE OF
-- THIS SOFTWARE, EVEN IF ADVISED OF THE POSSIBILITY OF SUCH DAMAGE.

Messages DEFINITIONS AUTOMATIC TAGS ::= BEGIN

-- Definitions for libpraefectus-level messages, excluding the high-level
-- message envelope.
--
-- The key words "MUST", "MUST NOT", "REQUIRED", "SHALL", "SHALL
-- NOT", "SHOULD", "SHOULD NOT", "RECOMMENDED", "MAY", and
-- "OPTIONAL" in this file are to be interpreted as per RFC 2119.
--
-- The concept of a "high-level message" is defined in
-- libpraefectus/DESIGN.txt.
--
-- "SHA-3" always refers to the Keccak hash function with the 256-bit
-- parameters, even if fewer than 256 bits will be generated from the result.
--
-- Many things dealing with instants and intervals are "application-defined"
-- because the rate at which instances actually advance is also
-- application-defined.
--
-- When a node is said to be "voting to DENY" some node, it means that the
-- node will vote for any valid vote to set the DENY status on that node,
-- as well as starting its own votes to do so. Such votes SHOULD be a few
-- seconds into the future and SHOULD be a round number (eg, evenly divisible
-- by 2 seconds) that other such nodes are likely to use, in order to maximise
-- the chance of the DENY carrying.
--
-- In general, if a message is received which violates an absolute requirement,
-- the node that received the message SHOULD begin voting to DENY the node that
-- created the message, and MUST not attempt to process the message. However,
-- it MUST count the message towards any hashing (both the in the hash tree and
-- for the purposes of commits) and SHOULD continue to proliferate the message
-- if it is not an RPC-type message. Some messages define other semantics for
-- the violation of hard requirements which take precedence over these general
-- rules.
--
-- Messages are classified as RPC-type, uncommitted redistributable, and
-- committed redistributable. Messages MUST be contained with envelopes of the
-- same type.

PraefDword      ::= INTEGER (0..4294967295)
PraefShort      ::= INTEGER (0..65535)
PraefByte       ::= INTEGER (0..255)
PraefPingId     ::= PraefDword
PraefNodeId     ::= PraefDword
PraefInstant    ::= PraefDword
PraefSerialNumber ::= PraefDword
PraefPubkey     ::= OCTET STRING SIZE(64)
PraefSignature  ::= OCTET STRING SIZE(32)
PraefHash       ::= OCTET STRING SIZE(32)
PraefHashPrefix ::= OCTET STRING SIZE(0..32)
PraefNetworkSalt ::= OCTET STRING SIZE(32)
PraefAdvSerNo   ::= PraefDword

-- Used to discover latency between nodes. A node SHOULD transmit a Ping
-- message to all other nodes at regular intervals. Upon receiving a Ping, the
-- receiver SHOULD immediateld transimit a a Pong containing the same id back
-- to the sender of the Ping. Nodes MAY begin voting to DENY a node which fails
-- to answer a certain number of consecutive Ping messages.
--
-- This an RPC-type message.
PraefMsgPing ::= SEQUENCE {
  -- The id of this ping, used to identify the corresponding Pong. This has no
  -- meaning to the receive, except that it determines the appropriate value
  -- for the field of the same name on the reply Pong message.
  --
  -- The value of this field SHOULD NOT be predictable.
  id            PraefPingId
}

-- An answer to a Ping message. Receivers SHOULD ignore the message if the id
-- does not correspond to that of a recently transmitted Ping message.
--
-- This is an RPC-type message.
PraefMsgPong ::= SEQUENCE {
  -- The id of the Ping that this Pong answers.
  id            PraefPingId
}

-- Identifies a node based upon network addresses. This is primarily used for
-- establishing routes.
PraefNetworkIdentifierPair ::= SEQUENCE {
  -- The network identifier of the host itself. Within a NAT, one might refer
  -- to this as the "LAN address" in some circles. Only nodes within the same
  -- physical network can expect to reach the node on this address.
  --
  -- Nodes with the same internet identifier SHOULD communicate via the address
  -- defined by the intranet identifier.
  intranet      PraefNetworkIdentifier,
  -- The network identifier of the node as perceived by an external party over
  -- the Internet. Nodes may generally expect to reach other nodes on the
  -- internet identifier; however, some NATs are buggy and will not route
  -- packets to their own external address correctly. Thus, nodes with the same
  -- internet identifier SHOULD use the intranet identifiers instead.
  --
  -- This field is OPTIONAL in "LAN games"; ie, those where all nodes are
  -- expected to be on the same physical network. It is REQUIRED for systems
  -- which are spread across the Internet.
  --
  -- If this field is present, the ip address contained MUST be of the same
  -- IP version as that of the intranet field.
  internet      PraefNetworkIdentifier OPTIONAL
}

-- An IP address / port pair.
PraefNetworkIdentifier ::= SEQUENCE {
  address       PraefIpAddress,
  port          PraefShort
}

-- Either an IPv4 or IPv6 address.
--
-- These are represented as octet strings rather than structured sequences
-- because it makes the interface produced by asn1c more tolerable.
PraefIpAddress ::= CHOICE {
  ipv4          OCTET STRING SIZE(4),
  -- The ipv6 address is a sequence of 8 16-bit integers, each encoded in
  -- network byte order.
  ipv6          OCTET STRING SIZE(16)
}

-- Requests basic information on the system in which the receiver is
-- participating. The receiver SHOULD reply to the given return address
-- with a NetworkInfo message. The receiver MUST process the message even
-- if the signature is not recognised, as this is used by nodes wishing to
-- join the system. The receiver MAY ignore the message if it does recognise
-- the signature, since it is assumed that members of the system are already
-- aware of the information that would be in the reply.
--
-- This is an RPC-type message. It SHOULD be the only compoment of the
-- high-level message; nodes MAY ignore GetNetworkInfo messages which do not
-- meet this requirement.
--
-- This is typically the first message sent by a prospective node. In NAT
-- environments, it must often be proxied by a third party. Prospective nodes
-- which do not receive a response after some timeout SHOULD retry sending it,
-- possibly to a different node known to be part of the system.
PraefMsgGetNetworkInfo ::= SEQUENCE {
  -- The network identifier that wishes to receive the information. This is not
  -- necessarily the same as the apparent source address, due to triangular
  -- routing needed to bootstrap Internet connections in NAT environments.
  retaddr       PraefNetworkIdentifierPair
}

-- Response to a GetNetworkInfo message. The contents MUST be correct, though a
-- prospective node has no way to validate them.
--
-- This response provides prospective nodes sufficient knowledge to begin
-- obtaining system state upon being accepted into the system, as well as to
-- calculate their id.
--
-- This is an RPC-type message.
PraefMsgNetworkInfo ::= SEQUENCE {
  -- Some random string of bytes used to salt hashes used for node id
  -- generation.
  salt          PraefNetworkSalt,
  -- A digital signature of the salt field (alone) generated with the bootstrap
  -- node's public key. This signature MUST be valid.
  --
  -- This field prevents a node from participating in a system with an invalid
  -- salt, which would lead to it diverging from the other nodes severely if a
  -- node joined using it. If the salt is wrong, either (a) the node will
  -- identify the fact that the signature is invalid and reject the message, or
  -- (b) will attempt to join with an incorrect bootstrap key, leading it to
  -- reject all messages it ever sees and eventually give up.
  saltsig       PraefSignature,
  -- The public key of the bootstrap node (ie, the one with id 1).
  bootstrapkey  PraefPubkey,
  -- The network identifier of the bootstrap node.
  bootstrapid   PraefNetworkIdentifierPair
}

-- Requests to join the system of which the receiver is a part. Receivers MUST
-- process this message if and only if they do not recognise the
-- signature. Upon reception of such a message from a node already in the
-- system, the JoinAccept that introduced that node SHOULD be
-- retransmitted. This MUST be the only message inside the high-level message
-- envelope, and the high-level message MUST NOT have tailing garbage. The
-- instant and advisory serial number on the high-level message MUST be zero.
--
-- Receiving nodes SHOULD accept the new node (with a JoinAccept). The sender
-- MAY reattempt this exact request if it receives no response after a certain
-- time-out, but MAY instead generate a new public key and restart with a
-- NetworkInfo message, generally to a different node known to be a part of the
-- system.
--
-- Receiving nodes MAY ignore this message if they have not recently received a
-- GetNetworkInfo message from the same return address, unless the application
-- is designed to bypass the GetNetworkInfo/NetworkInfo exchange by using a
-- more secure method.
--
-- Acceptance of the new node is performed by broadcasting a JoinAccept message
-- to all nodes, including the new one.
--
-- This is an RPC-type message.
PraefMsgJoinRequest ::= SEQUENCE {
  -- The public key of the node requesting to join. The signature on the
  -- containing high-level message envelope MUST be valid by this signature.
  --
  -- Additionally, this value MUST NOT be the same as the public key used by
  -- the bootstrap node. In practise, the only conceivable way for this
  -- constraint to be violated while still producing a valid signature is if
  -- the bootstrap node attempts to join its own system with the same key.
  publickey     PraefPubkey,
  -- The network address pair with which this node will communicate.
  identifier    PraefNetworkIdentifierPair,
  -- An optional application-defined authentication structure. This can be used
  -- for purposes such as password-protected LAN games or secured Internet
  -- games.
  --
  -- For example, a password-protected lan game could be effected by embedding
  -- the following structure within this field:
  --
  -- SEQUENCE {
  --   hmac     OCTET STRING SIZE(26)
  -- }
  --
  -- Where hmac is the HMAC of the node's public key and the secret password.
  --
  -- If the application-defined semantics reject this value, the node SHALL NOT
  -- be accepted into the system, and the node that received this request MUST
  -- NOT send a JoinAccept message to any peer.
  auth          OCTET STRING SIZE(1..58) OPTIONAL
}

-- Joins a new node to the system.
--
-- In this model of joining, the node's public key and a system-specific salt
-- are hashed to produce a hopefully-unique id for the new node. Specifically,
-- this hash is the first 32 bits (interpreted as a little-endian integer)
-- output by SHA-3 after inputing the system's salt and the public key of the
-- new node. If this would produce an id of 0 or 1, the value 2 is used
-- instead. Furthermore, if the id this process would produce is otherwise
-- reserved by the application, the next id in sequence is used.
--
-- This SHOULD be the only message within the containing high-level message,
-- and the containing high-level message MUST NOT exceed 240 bytes in length.
--
-- This is an uncommitted redistributable message.
PraefMsgJoinAccept ::= SEQUENCE {
  -- The original JoinRequest message, used to validate the signature.
  request       PraefMsgJoinRequest,
  -- The timestamp on the original JoinRequest
  instant       PraefInstant,
  -- The signature of the high-level message envelope containing the original
  -- JoinRequest message, calculated by composing the most compact such
  -- high-level message possible with instant and advisory serial number 0. The
  -- signature MUST be valid.
  signature     PraefSignature
}

-- Requests the contents of a high-level message which represented the
-- acceptance of a new node into the system.
--
-- The receiver SHOULD immediately answer with an appropriate JoinTreeEntry.
--
-- This is normally only used by newly-joined nodes to quickly discover all the
-- public keys.
--
-- This is an RPC-type message.
PraefMsgJoinTree ::= SEQUENCE {
  -- The id of the node which hypothetically accepted a new node into the
  -- system.
  node          PraefNodeId,
  -- The offset of the message within the receiver's list of messages from the
  -- given node which contained an acceptance of another node. No particular
  -- sequence is defined, but it SHOULD be consistent for any given node,
  -- starting at zero and increasing by one for each message.
  offset        PraefDword
}

-- A response to a JoinTree request.
--
-- Spurious JoinTreeEntry messages MUST be silently ignored.
--
-- This is an RPC-type request.
PraefMsgJoinTreeEntry ::= SEQUENCE {
  -- The node id sent in the corresponding JoinTree message.
  node          PraefNodeId,
  -- The offset sent in the corresponding JoinTree message.
  offset        PraefDword,
  -- An advisory number indicating how many keys the receiver might expect to
  -- receive from the sender via JoinTree traversal. The intent of this field
  -- is for progress reporting.
  nkeys         PraefDword,
  -- A high-level message which SHOULD contain an acccptance by the input node
  -- of another node. Note that compliant JoinAccept messages always fit within
  -- this field.
  --
  -- The absence of this field indicates that offset is beyond the end of the
  -- list.
  data          OCTET STRING SIZE(44..240) OPTIONAL
}

-- Votes to set a a status bit on a node.
--
-- A chmod carries when at least half of the nodes which are alive (have GRANT
-- but do not have DENY) cast identical votes. Nodes MUST correctly handle
-- retroactive result changes based upon messages received after the fact or
-- network topology changes.
--
-- Further details of how chmod events work, as well as the node status model,
-- can be found in the documentation for metatransactor (see
-- libpraefectus/metatransactor.h).
--
-- This is a committed redistributable message.
PraefMsgChmod ::= SEQUENCE {
  -- The node to be affected by this change. If the receiver does not know of
  -- a node with this id, it MUST act as if it never received the containing
  -- high-level message.
  node          PraefNodeId,
  -- The instant at which the status bit will be set. This MUST be greater than
  -- or equal to the timestamp on the high-level message timestamp, and MUST
  -- not exceed the timestamp on the high-level message by a certain
  -- application-defined threshold.
  effective     PraefInstant,
  -- The bit which is to be set on the node if this vote carries.
  bit           ENUMERATED { grant, deny }
}

-- Specifies an application-defined event to be passed into the
-- application-level context. It is up to the application to provide the means
-- to decode the message and to provide the pessimistic/optimistic parameters
-- and the optimistic deadline, as appropriate.
--
-- The object id of the event is implicitly the id of the node that produced
-- this message. The instant of the event is implicitly the instant on the
-- envelope of the high-level message.
--
-- While the receiver MAY tentatively accept the new event, it MUST eventually
-- reject the message if fewer than half of the nodes in the system cast a Vote
-- message for this event. Nodes MUST correctly handle retroactive changes to
-- this acceptance based upon untimely message reception or incorrect topology
-- data. The full semantics for voting are described in the transactor
-- documentation (see libpraefectus/transactor.h).
--
-- This is a committed redistributable message.
PraefMsgAppEvent ::= SEQUENCE {
  -- The serial number for this event. The (node,instant,serialnumber) triple
  -- MUST uniquely identify this event. If the sender creates a conflict, the
  -- receiver MUST remove the existing event with the same identifier from its
  -- state, and additionally not add this event, but MUST otherwise accept the
  -- message. In such a case, the node SHOULD start voting to DENY the node
  -- that created this conflict.
  serialnumber  PraefSerialNumber,
  -- The encoded form of the application event. How to decode this is
  -- application-specific.
  data          OCTET STRING SIZE(1..248)
}

-- Indicates that the sender wishes to accept a particular event.
--
-- More information on voting can be found in the documentation for the
-- AppEvent message and in the transactor documentation (see
-- libpraefectus/transactor.h).
--
-- Nodes MUST accept Votes which specify nonexistent events and eventually
-- apply them if the event comes into existence.
--
-- A node MUST NOT send more than one Vote message for each Event message.
--
-- This is a committed redistributable event.
PraefMsgVote ::= SEQUENCE {
  -- The node which sent the event that this message votes for.
  node          PraefNodeId,
  -- The instant of the event being voted for. This SHOULD be less than or
  -- equal to the instant of the high-level message, and MUST not be beyond a
  -- certain application-defined distance into the past or the future (with
  -- respect to the time on the envelope).
  instant       PraefInstant,
  -- The serial number of the event being voted for.
  serialnumber  PraefSerialNumber
}

-- Indicates that the sender is committing to a particular set of of committed
-- redistributable messages within a particular timespan, starting from some
-- specified instant to the instant of the high-level message (both inclusive).
--
-- Commits from the same node MUST NOT have overlapping timespans.
--
-- A node MUST continue processing committed redistributable messages even if
-- it can prove that the commit will never be fulfilled.
--
-- More information on how commits can be used can be found in the
-- commitment-chain documentation (see limpraefectus/commitment-chain.h).
--
-- This is an uncommitted redistributable message.
PraefMsgCommit ::= SEQUENCE {
  -- The instant at which the commit range starts. This MUST be less than or
  -- equal to the instant on the high-level message.
  start         PraefInstant,
  -- The hash of the messages in this commit. This is the SHA-3 obtained by
  -- concatenating all committed redistributable high-level messages within the
  -- commit's timespan, in ascending order by each message's respective
  -- hash. The message hash is the SHA-3 of the high-level message itself.
  hash          PraefHash
}

-- Requests a listing of a directory within the receiver's hash tree.
--
-- Nodes MUST maintain a hash tree of all redistributable messages they have
-- received. The hash of each message within the tree is the SHA-3 of the whole
-- high-level message. The hash tree itself is organised into directories and
-- objects.
--
-- Each directory corresponds to some prefix of nybbles from message hashes,
-- and has 16 entries. Each entry can be empty, refer to an object, or refer to
-- a subdirectory. The root directory (with a prefix of 0 nybbles) is always a
-- directory, even if it is empty. Entries in a directory may only be a
-- subdirectory if that subdirectory directly or indirectly contains more than
-- one object.
--
-- Objects (ie, serialised messages) are identified by a 32-bit integer which
-- is particular to the node maintaining that tree. Other nodes can learn these
-- identifiers by traversing the tree.
--
-- Subdirectory entries are associated with a 32-bit SHA-3 hash of their
-- contents. The input for this hash is the concatenation of the hashes of
-- objects which are direct entries within the directory and the hashes of
-- direct subdirectory entries. These are concatenated in the order they
-- occur in the directory (ie, object and directory hashes can be
-- interspersed). These 32-bit hashes allow for rapidly locating which parts of
-- the hash tree are inconsistent between two nodes.
--
-- Nodes SHOULD maintain snapshots of their hash trees at well-known intervals
-- into the past in order to maximise the consistency between different nodes'
-- snapshots. It is RECOMMENDED that snapshots be kept at fixed,
-- application-defined deltas, where the instant for a delta is the greatest
-- instant evenly divisible by delta which is also at least delta instants in
-- the past. (At 64 instants/second, good values for delta may be 16, 32, 64,
-- 128, and 196.)
--
-- This particular message requests a listing of a directory within the other
-- node's hash tree. The receiver SHOULD respond with a sensible HtDir
-- message. If the named directory does not exist, no response is necessary.
--
-- The root directory is always expected to be available, as is any directory
-- the responder indicates to be present. Nodes MAY begin voting to DENY a node
-- which fails some consecutive number of times to respond to HtLs messages
-- that are expected to elicit a response.
--
-- This is an RPC-type message.
PraefMsgHtLs ::= SEQUENCE {
  -- The snapshot that the requester would like to compare against. The
  -- responder SHOULD produce a response by looking at the latest snapshot
  -- before this instant, or the earliest snapshot available if this is before
  -- all snapshots it maintains.
  snapshot      PraefInstant,
  -- The hash prefix for the given directory. The final nybble in the prefix
  -- may or may not be meaningful, depending on the lownybble field.
  --
  -- The empty prefix refers to the root directory.
  hash          PraefHashPrefix,
  -- Whether the final nybble in hash is actually part of the prefix. If this
  -- is false, the final 4 bits of hash are ignored. This field is meaningless
  -- if hash is empty.
  lownybble     BOOLEAN
}

-- Informs the receiver of the contents of a hash tree directory in one of the
-- sender's hash tree snapshots.
--
-- This is an RPC-type message.
PraefMsgHtDir ::= SEQUENCE {
  -- An HtLs message to which this is (in theory) a response. As much as
  -- possible, it SHOULD be the exact contents of an actual HtLs message
  -- received, though nodes MAY send gratuitous HtDir messages at any time.
  request       PraefMsgHtLs,
  -- The first 32 bits of the SHA-3 of the concatenation of the SHA-3 hashes of
  -- all objects contained *directly* by this subdirectory followed by the
  -- public key of the recipient of this message followed by the snapshot on
  -- the htls object encoded as a 4-byte little-endian integer, itself
  -- interpreted as a little-endian integer.
  --
  -- This field exists to resolve the case where two nodes each have a
  -- directory containing objects in the same slots, but which are actually
  -- different, only coincidentally having the same prefix. This case can be
  -- detected with overwhelming probability by detecting that the objhash on
  -- the whole directory differs, in which case the node that notices this
  -- SHOULD simply request all objects in the directory.
  --
  -- In theory, this field is vulnerable to birthday attacks, which could cause
  -- a system to diverge. However, directories near the top of the tree are
  -- subject to effectively random pollution by other nodes that will quickly
  -- resolve such situations by producing actual prefix collisions that split
  -- the objects into distinct subdirectories; deeper directories require
  -- exponentially more work since the objects in question also must have a
  -- given SHA-3 prefix. Salting the hash with the recipient's public key makes
  -- it impossible to precompute an attack at deeper levels, and also means
  -- that any attack must work simultaneously against *all* cooperating nodes
  -- in the system.
  --
  -- Furthermore, salting via the snapshot instant (which can be relied on to
  -- update appropriately, as this mechism defends two *cooperating* nodes)
  -- means that any hypothetical attack can generally only work at exactly one
  -- instant; making it work on more than one requires exponentially more
  -- time.
  objhash       PraefDword,
  -- The entries present in this directory, indexed by the first nybble of
  -- objects after the hash prefix of the containing directory.
  entries       SEQUENCE SIZE(16) OF PraefHtdirEntry
}

-- A single hash tree directory entry.
PraefHtdirEntry ::= CHOICE {
  -- Indicates that this entry has no content.
  empty         NULL,
  -- Indicates that this entry has a direct object, and specifies the
  -- node-specific id of that object.
  objectid      PraefDword,
  -- Indicates that this entry is a subdirectory, and specifies a 32-bit hash
  -- of that subdirectory entry. This 32-bit hash is the first 32 bits of the
  -- SHA-3 of the internal 64-bit directory hash (as defined in hash-tree.h)
  -- encoded as a little-endian integer concatenated with the public key of the
  -- recipient of the message concatenated with the instant of the htls on the
  -- enclosing response encoded as a 32-bit little-endian integer.
  --
  -- The additional hash steps allow reducing this field to 32-bit without
  -- opening it up to viable birthday attacks.
  --
  -- Note that in theory this field is still susceptible to vanilla birthday
  -- attacks against the underlying 64-bit hash. However, this is subject to
  -- having matching hash prefixes, which makes the attack geometrically more
  -- difficult as the attack moves deeper into the tree. An attack will not
  -- work near the top of the tree since other messages will pollute the
  -- directories (ie, the attacker needs full control over the directory of
  -- attack). An attack on a subdirectory of a level-two directory (8 bit
  -- prefix + 4 bit offset) is expected to require 24.5 trillion plaintexts to
  -- succeed. Each level lower multiplies this requirement by a factor of
  -- 16. Applications can make such attacks even less practical by deliberately
  -- producing messages to rapidly pollute the upper levels of the tree.
  subdirsid     PraefDword
}

-- Requests the receiver to retransmit the high-level message associated with
-- the object of the given id in the receiver's hash tree. The receiver does
-- not need to be the original author of this message.
--
-- Unless the receiver has some reason not to, it SHOULD send the high-level
-- message identified by the given id to the receiver verbatim. Note that there
-- is no special envelope for this response, so there is no message type for
-- it. Rather, the original requester simply receives the original message
-- without needing to associate it back to an HtRead request.
--
-- Nodes SHOULD define time-based rules as to what objects they are willing to
-- transmit via this request. For example, one typically will not want to
-- reveal committed redistributable messages that were introduced after the
-- commit threshold of the requester (see libpraefectus/commitment-chain.h for
-- details on this terminology).
--
-- Nodes SHOULD NOT begin voting to DENY another node on the suspicion that
-- they have not received a response to this request.
--
-- This is an RPC-type message.
PraefMsgHtRead ::= SEQUENCE {
  objectid      PraefDword
}

-- Reqeuests the receiver to act as if it had received a large number of HtRead
-- requests for objects with particular hashes.
--
-- The same recommendations as for HtRead with respect to limiting visibility
-- of committed redistributable messages applies here as well.
--
-- An HtRange specifies a base hash as well as some filter parameters. The
-- receiver SHOULD look up what objects match these parameters (up to some
-- maximum number of objects) and transmit them to the requester.
--
-- The receiver, regardless of whether it transmits any results from this
-- request, SHOULD respond with a PraefMsgHtRangeNext in order to assist the
-- requester with state tracking and to inform it when it has fully queried the
-- hash tree. The sender MAY interpret the lack of an HtRangeNext as an
-- indication that the HtRange query was not received and thus retransmit this
-- query.
--
-- This is an RPC-type message.
PraefMsgHtRange ::= SEQUENCE {
  -- The minimum hash that the requester is interested in. This is expanded to
  -- a full hash by padding it to the right with zeroes. The receiver SHOULD
  -- NOT retransmit messages whose hash would precede this hash.
  hash          PraefHashPrefix,
  -- offset and mask control which messages may be retransmitted, allowing a
  -- range query to be performed across multiple nodes. An object matches the
  -- range filter only if, given the final byte of the object hash h,
  -- ((h & mask) == offset).
  offset        PraefByte,
  mask          PraefByte,
  -- An arbitrary integer identifier for this query, to be sent on the
  -- corresponding HtRangeNext message. This MAY be predictable, though no
  -- sequence is defined.
  id            PraefByte
}

-- Informs the receiver about the result of a prior HtRange query. In
-- particular, it informs the receiver about what range was satisfied by the
-- original HtRange query and whether any further queries would be useful.
--
-- It also provides the recipient with sufficient information to determine with
-- high confidence whether all messages produced by the HtRange query were
-- received.
--
-- This is an RPC-type message.
PraefMsgHtRangeNext ::= SEQUENCE {
  -- The suggested hash prefix for the next HtRange query to be performed by
  -- the receiver against the sender. The receiver SHOULD ignore HtRangeNext
  -- messages indicating a hash in a range they have already queried. If no
  -- hash is given in this message, the sender indicates that it believes the
  -- receiver has exhausted the results produceable by HtRange queries,
  -- assuming that the sender scanned the ranges sequentially.
  --
  -- The sender SHOULD return the minimal prefix hash that would identify the
  -- first message it chose not to send.
  hash          PraefHashPrefix OPTIONAL,
  -- The id of the corresponding HtRange request.
  id            PraefByte,
  -- Specifies a bloom filter which can be used by the recipient to determine
  -- whether it has learned of all the messages that the sender thinks it
  -- should have.
  --
  -- Bit zero is the lowest bit of the zeroth octet. Each message is assigned
  -- eleven hashes. Each hash takes its 8 lowest bits from a byte in the
  -- message's SHA-3 hash and its 2 upper bits from the lowest 2 bits in the
  -- next byte in the SHA-3 hash to the left. All hashes draw from the 22
  -- right-most octets of the SHA-3 hash.
  --
  -- In order to test whether all messages have been received, the recipient
  -- runs the range query that this message answers against its own hash tree
  -- and builds a bloom filter with the same properties, truncating the
  -- messages to the range terminated by the hash field, if present. If any
  -- bits in this value are set which are not set in the recipient's bloom
  -- filter, it has definitely lost messages and should retry the HtRange.
  --
  -- If HtRanges are answered with a maximum of 64 messages per query, and all
  -- nodes which answer HtRanges are relatively in-sync, a lost message has a
  -- 0.04% chance of being undetected by this message. If 32 messages are sent
  -- per query, this reduces to 0.00015%.
  bloom         OCTET STRING SIZE(128)
}

-- Informs the receiver that the sender is not currently in a good position to
-- service HtRange requests, so the receiver should stop trying to perform such
-- queries against it.
--
-- This is an RPC-type message.
PraefMsgHtRangeUnknown ::= NULL

-- Advises the receiver of a bitmap of affirmative and negative
-- acknowledgements of message reception from another node (which may be the
-- receiver or some other node), according to the advisory serial numbers on
-- the messages.
--
-- The receiver SHOULD check each negatively-acknowledged advisory serial
-- number (if it still maintains an advisory serial number table for that node
-- in that era) and forward any such messages it is aware of back to the
-- sender, unless the messages would be hidden by the same rules governing
-- HtRead, or if the time of the messages is later than the time of this
-- request (since the node likely has received such a message by the time this
-- request is received).
--
-- This is a faster way to redistribute lost messages than the hash-tree
-- system, but relies on the original sender making a best effort to use
-- advisory serial numbers optimally.
--
-- The RECOMMENDED usage of this message is to broadcast one per node from
-- which the sending node has received messages on fixed intervals, eg, 2 times
-- per second, with a more frequent unicast to the originating node (eg, 4
-- times per second). Generally, the receiver starts base at the first advisory
-- serial number that has *not* been received, since affirmative
-- acknowledgements have little effect.
--
-- A node which retransmits a message in response to this message SHOULD mark
-- that message as positively acknowledged, even without a Received message
-- saying so. Receivers SHOULD NOT allow a Received message to change the
-- status of a tracked message from positive to negative acknowledgement.
--
-- This is an RPC-type message.
PraefMsgReceived ::= SEQUENCE {
  -- The node from which listed advisory serial numbers were generated
  node          PraefNodeId,
  -- The first advisory serial number being acknowledged (either positively or
  -- negatively).
  base          PraefAdvSerNo,
  -- The number of serial numbers before base that the sender asserts have not
  -- changed status since the last Received message it sent. The receiver
  -- SHOULD interpret anything formerly negatively acknowledged in this range
  -- which it still track to be another negative acknowledgement.
  negoff        INTEGER (0..1023),
  -- A bitmap of messages within the range that have been received. The range
  -- is defined to be from base, inclusive, to (base + sizeof(received)*8),
  -- exclusive, modulo 2**32. The lowest bit of the first octet corresponds to
  -- base. A 1 bit indicates that the sender had received the given message as
  -- of the time of this message; a 0 bit indicates that the sender had not.
  --
  -- (This is not a BIT STREAM or a SEQUENCE OF BOOLEAN because it produces a
  -- more compact encoding and is simpler to work with.)
  received      OCTET STRING SIZE(1..128)
}

-- Informs the recipient that the sender has received every
-- committed-redistributable and uncommitted-redistributable message the
-- recipient produced up to and including a certain limit.
--
-- This mechanism only works if the recipient sends its first UR or CR message
-- with serial number 0, and increments serial numbers by 1 for each
-- consecutive UR or CR message, with RPC serial numbers being in a different
-- space.
--
-- Upon receiving this message, the receiver SHOULD retransmit messages it
-- believes the sender should already have which are beyond the limit.
--
-- This mechanism exists because the HtRange scan on node connection will
-- typically interfere with the Received mechanism, leading to a "hole" of
-- messages which came into existence immediately beyond the visibility
-- threshold of the HtRange responses. It allows nodes to work with another
-- node to quickly recover their own holes.
--
-- This is an RPC-type message.
PraefMsgAck ::= SEQUENCE {
  -- The intended recipient of this message. The receiver MUST ignore this
  -- message if this id differs from its own.
  recipient     PraefNodeId,
  -- The last consecutive serial number that the sender has seen attached to
  -- any CR or UR message from the recipient.
  max           PraefAdvSerNo
}

-- Sends an application-defined unicast message to the receiving node.
--
-- This is an RPC-type message.
PraefMsgAppUnicast ::= SEQUENCE {
  -- The application-defined message.
  data          OCTET STRING SIZE(1..250)
}

-- Indicates that the sender believes it is maintaining active communication
-- with another node.
--
-- A route from one node to a particular identifier is considered active if a
-- Route message has been received for that pair with a timestamp within some
-- application-defined timeout.
--
-- Nodes SHOULD regularly publish Route messages for every route they hold
-- open, and only do so if they have received RPC messages from that network
-- address with recent timestamps. This excepts nodes which have the DENY
-- status set, or which have not gained the GRANT status after some time. Nodes
-- SHOULD try to establish routes to destinations of which they learn from
-- other nodes' Route messages.
--
-- This is an RPC-type message.
PraefMsgRoute ::= SEQUENCE {
  -- The id of a node with which the sender is holding a connection. The
  -- receiver MUST take no special action against the sender if it does not
  -- know about the given node id, even if it knows the id is not permitted.
  --
  -- The receiver SHOULD reply with a WhoIs message if it does not recognise
  -- the node id.
  node          PraefNodeId,
  -- The estimated latency between the source node and the destination of this
  -- route, in instants. This is purely advisory.
  latency       PraefByte
}

-- Indicates that the sender has reason to believe that a node with the given
-- id may exist, but does not itself know about it.
--
-- If the receiver has the Accept message corresponding to the named node, it
-- SHOULD retransimit it to the sender. If the receiver does not know about the
-- node either, it MUST NOT take any special action.
--
-- This is an RPC-type message.
PraefMsgWhoIs ::= SEQUENCE {
  -- The id of the node being queried.
  node          PraefNodeId
}

PraefMsg ::= CHOICE {
  ping          PraefMsgPing,
  pong          PraefMsgPong,
  getnetinfo    PraefMsgGetNetworkInfo,
  netinfo       PraefMsgNetworkInfo,
  joinreq       PraefMsgJoinRequest,
  accept        PraefMsgJoinAccept,
  chmod         PraefMsgChmod,
  vote          PraefMsgVote,
  appevt        PraefMsgAppEvent,
  commit        PraefMsgCommit,
  htls          PraefMsgHtLs,
  htdir         PraefMsgHtDir,
  htread        PraefMsgHtRead,
  htrange       PraefMsgHtRange,
  htrangenext   PraefMsgHtRangeNext,
  htrangeunk    PraefMsgHtRangeUnknown,
  jointree      PraefMsgJoinTree,
  jtentry       PraefMsgJoinTreeEntry,
  received      PraefMsgReceived,
  ack           PraefMsgAck,
  appuni        PraefMsgAppUnicast,
  route         PraefMsgRoute,
  whois         PraefMsgWhoIs
}


END
