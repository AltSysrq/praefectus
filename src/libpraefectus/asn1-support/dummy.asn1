-- This module exists mainly to get asn1c to pull in everything we need.
Dummy DEFINITIONS ::= BEGIN
PraefDummy ::= SEQUENCE {
  dummyseq SEQUENCE OF INTEGER,
  dummyset SET OF INTEGER
}

PraefDummyChoice ::= CHOICE {
  dummy PraefDummy,
  other ENUMERATED { foo, bar },
  bool BOOLEAN,
  null NULL,
  chars VisibleString,
  mchars PrintableString,
  utf8 UTF8String
}

PraefDummySet ::= SET {
  null NULL
}

END
