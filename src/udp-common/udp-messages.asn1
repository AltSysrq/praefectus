---
-- Copyright (c) 2014 Jason Lingle
-- All rights reserved.
--
-- Redistribution and use in source and binary forms, with or without
-- modification, are permitted provided that the following conditions
-- are met:
-- 1. Redistributions of source code must retain the above copyright
--    notice, this list of conditions and the following disclaimer.
-- 2. Redistributions in binary form must reproduce the above copyright
--    notice, this list of conditions and the following disclaimer in the
--    documentation and/or other materials provided with the distribution.
-- 3. Neither the name of the author nor the names of its contributors
--    may be used to endorse or promote products derived from this software
--    without specific prior written permission.
--
-- THIS SOFTWARE IS PROVIDED BY THE AUTHOR ``AS IS'' AND ANY EXPRESS OR
-- IMPLIED WARRANTIES, INCLUDING, BUT NOT LIMITED TO, THE IMPLIED WARRANTIES
-- OF MERCHANTABILITY AND FITNESS FOR A PARTICULAR PURPOSE ARE DISCLAIMED.
-- IN NO EVENT SHALL THE AUTHOR BE LIABLE FOR ANY DIRECT, INDIRECT,
-- INCIDENTAL, SPECIAL, EXEMPLARY, OR CONSEQUENTIAL DAMAGES (INCLUDING, BUT
-- NOT LIMITED TO, PROCUREMENT OF SUBSTITUTE GOODS OR SERVICES; LOSS OF USE,
-- DATA, OR PROFITS; OR BUSINESS INTERRUPTION) HOWEVER CAUSED AND ON ANY
-- THEORY OF LIABILITY, WHETHER IN CONTRACT, STRICT LIABILITY, OR TORT
-- (INCLUDING NEGLIGENCE OR OTHERWISE) ARISING IN ANY WAY OUT OF THE USE OF
-- THIS SOFTWARE, EVEN IF ADVISED OF THE POSSIBILITY OF SUCH DAMAGE.

UdpMessages DEFINITIONS AUTOMATIC TAGS ::= BEGIN

-- Definitions for UDP-level messages, used by both the UDP message bus and the
-- triangular router.
--
-- libpraefectus messages are in normal conditions transimitted without being
-- wrapped by anything defined in this file.

-- Defined by libpraefectus: PraefDword, PraefShort, PraefByte,
-- PraefIpAddress, PraefNetworkIdentifier, PraefNetworkIdentifierPair.

-- Sent to hosts (generally broadcast on LAN or sent to the vertex server) to
-- solicit Advertise responses to discover what compatible systems currently
-- exist.
PraefUdpMsgDiscover ::= SEQUENCE {
  -- The name of the application performing the discovery. Applications other
  -- than the one listed MUST ignore such discoveries.
  application   PrintableString SIZE(1..16),
  -- The version of the application performing the discovery. Generally,
  -- applications of a different version SHOULD ignore such discoveries.
  version       PrintableString SIZE(1..8)
}

-- Unicast to hosts in response to Discover messages.
PraefUdpMsgAdvertise ::= SEQUENCE {
  -- A hopefully-unique identifier of the system that this message is
  -- advertising, so that the receiver can deduplicate Advertise responses.
  sysid         PraefDword,
  -- The network identifier pair of the sender.
  netid         PraefNetworkIdentifierPair,
  -- Arbitrary application-defined data about the state of the system being
  -- advertised.
  data          OCTET STRING SIZE(0..1023)
}

-- Sent to the vertex server to request a YouAre response.
PraefUdpMsgWhoAmI ::= SEQUENCE {
  -- Identifies the local component of the sender's identifier pair.
  local         PraefNetworkIdentifier
}

-- Sent by the vertex server in response to a WhoAmI.
PraefUdpMsgYouAre ::= SEQUENCE {
  -- The full identifier pair, including the recipient's Internet address.
  netid         PraefNetworkIdentifierPair
}

-- Registers an advertisement on the vertex server.
PraefUdpMsgRegister ::= SEQUENCE {
  -- The expected discovery packet to which the advertisement would be a
  -- response.
  fordiscovery  PraefUdpMsgDiscover,
  -- The response to send whenever a matching discover is received.
  respondwith   PraefUdpMsgAdvertise
}

-- Sent to the vertex server to perform triangular routing to another host. The
-- vertex server will not route to a host it is not in active communication
-- with.
PraefUdpMsgEcho ::= SEQUENCE {
  -- The Internet address of the host that is to receive the payload.
  dst           PraefNetworkIdentifierPair,
  -- The payload to send to the chosen host.
  data          OCTET STRING SIZE(0..511)
}

PraefUdpMsg ::= CHOICE {
  discover      PraefUdpMsgDiscover,
  advertise     PraefUdpMsgAdvertise,
  whoami        PraefUdpMsgWhoAmI,
  youare        PraefUdpMsgYouAre,
  register      PraefUdpMsgRegister,
  echo          PraefUdpMsgEcho,
  ping          NULL
}

END
